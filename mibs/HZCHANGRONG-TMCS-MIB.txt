--
-- HZCHANGRONG-TMCS-MIB.my
-- MIB generated by MG-SOFT Visual MIB Builder Version 6.0  Build 88
-- Friday, September 20, 2019 at 15:26:11
--

	HZCHANGRONG-TMCS-MIB DEFINITIONS ::= BEGIN
 
		IMPORTS
			OBJECT-GROUP, NOTIFICATION-GROUP			
				FROM SNMPv2-CONF			
			enterprises, Unsigned32, OBJECT-TYPE, MODULE-IDENTITY, OBJECT-IDENTITY, 
			NOTIFICATION-TYPE			
				FROM SNMPv2-SMI;
	
	
		-- 1.3.6.1.4.1.826318
		tmcsMIB MODULE-IDENTITY 
			LAST-UPDATED "201909121644Z"		-- September 12, 2019 at 16:44 GMT
			ORGANIZATION 
				"www.hzchangrong.com."
			CONTACT-INFO 
				"wh08420@outlook.com."
			DESCRIPTION 
				"MIB for Remote Control and Monitoring System of hangzhou changrong Co., LTD."
			REVISION "201908161308Z"		-- August 16, 2019 at 13:08 GMT
			DESCRIPTION 
				"The first version."
			::= { enterprises 826318 }

		
	
--
-- Node definitions
--
	
		-- 1.3.6.1.4.1.826318.1
		tmcsMIBObjects OBJECT-IDENTITY
			STATUS current
			DESCRIPTION 
				"Description."
			::= { tmcsMIB 1 }

		
		-- 1.3.6.1.4.1.826318.1.1
		tmcsMIBScalars OBJECT IDENTIFIER ::= { tmcsMIBObjects 1 }

		
		-- 1.3.6.1.4.1.826318.1.2
		tmcsMIBTables OBJECT IDENTIFIER ::= { tmcsMIBObjects 2 }

		
--  设备信息表定义
		-- 1.3.6.1.4.1.826318.1.2.1
		devInfoTable OBJECT-TYPE
			SYNTAX SEQUENCE OF DevInfoEntry
			MAX-ACCESS not-accessible
			STATUS current
			DESCRIPTION
				"Description."
			::= { tmcsMIBTables 1 }

		
--  设备号区分唯一的设备
		-- 1.3.6.1.4.1.826318.1.2.1.1
		devInfoEntry OBJECT-TYPE
			SYNTAX DevInfoEntry
			MAX-ACCESS not-accessible
			STATUS current
			DESCRIPTION
				"Description."
			INDEX { devNum }
			::= { devInfoTable 1 }

		
		DevInfoEntry ::=
			SEQUENCE { 
				devNum
					Unsigned32,
				devType
					INTEGER,
				devName
					OCTET STRING
			 }

--  设备号，范围暂定1～128
		-- 1.3.6.1.4.1.826318.1.2.1.1.1
		devNum OBJECT-TYPE
			SYNTAX Unsigned32 (1..128)
			MAX-ACCESS read-only
			STATUS current
			DESCRIPTION
				"Description."
			::= { devInfoEntry 1 }

		
--  设备类型：0表示服务器；1表示LIU
		-- 1.3.6.1.4.1.826318.1.2.1.1.2
		devType OBJECT-TYPE
			SYNTAX INTEGER
				{
				serv(0),
				liu(1)
				}
			MAX-ACCESS read-only
			STATUS current
			DESCRIPTION
				"Description."
			::= { devInfoEntry 2 }

		
--  设备名称，名称长度最大16字节
		-- 1.3.6.1.4.1.826318.1.2.1.1.3
		devName OBJECT-TYPE
			SYNTAX OCTET STRING (SIZE (1..16))
			MAX-ACCESS read-only
			STATUS current
			DESCRIPTION
				"Description."
			::= { devInfoEntry 3 }

		
--  主控板信息表定义
		-- 1.3.6.1.4.1.826318.1.2.2
		mpuInfoTable OBJECT-TYPE
			SYNTAX SEQUENCE OF MpuInfoEntry
			MAX-ACCESS not-accessible
			STATUS current
			DESCRIPTION
				"Description."
			::= { tmcsMIBTables 2 }

		
--  主控板的设备号和槽位号区分唯一的主控板
		-- 1.3.6.1.4.1.826318.1.2.2.1
		mpuInfoEntry OBJECT-TYPE
			SYNTAX MpuInfoEntry
			MAX-ACCESS not-accessible
			STATUS current
			DESCRIPTION
				"Description."
			INDEX { devNumOfMpu, slotNumOfMpu }
			::= { mpuInfoTable 1 }

		
		MpuInfoEntry ::=
			SEQUENCE { 
				devNumOfMpu
					Unsigned32,
				slotNumOfMpu
					Unsigned32,
				mpuStatus
					INTEGER
			 }

--  主控板所在设备的设备号，对应devInfoTable中定义的devNum
		-- 1.3.6.1.4.1.826318.1.2.2.1.1
		devNumOfMpu OBJECT-TYPE
			SYNTAX Unsigned32 (1..128)
			MAX-ACCESS read-only
			STATUS current
			DESCRIPTION
				"Description."
			::= { mpuInfoEntry 1 }

		
--  主控板槽位号，一个LIU单元只有2块主控板，用槽位号1和2区分
		-- 1.3.6.1.4.1.826318.1.2.2.1.2
		slotNumOfMpu OBJECT-TYPE
			SYNTAX Unsigned32 (1..2)
			MAX-ACCESS read-only
			STATUS current
			DESCRIPTION
				"Description."
			::= { mpuInfoEntry 2 }

		
--  主控板状态：0表示故障；1表示正常
		-- 1.3.6.1.4.1.826318.1.2.2.1.3
		mpuStatus OBJECT-TYPE
			SYNTAX INTEGER
				{
				malfunction(0),
				normal(1)
				}
			MAX-ACCESS read-only
			STATUS current
			DESCRIPTION
				"Description."
			::= { mpuInfoEntry 3 }

		
--  用户板信息表定义
		-- 1.3.6.1.4.1.826318.1.2.3
		riuInfoTable OBJECT-TYPE
			SYNTAX SEQUENCE OF RiuInfoEntry
			MAX-ACCESS not-accessible
			STATUS current
			DESCRIPTION
				"Description."
			::= { tmcsMIBTables 3 }

		
--  用户板的框号和槽位号区分唯一的主控板
		-- 1.3.6.1.4.1.826318.1.2.3.1
		riuInfoEntry OBJECT-TYPE
			SYNTAX RiuInfoEntry
			MAX-ACCESS not-accessible
			STATUS current
			DESCRIPTION
				"Description."
			INDEX { frameNumOfRiu, slotNumOfRiu }
			::= { riuInfoTable 1 }

		
		RiuInfoEntry ::=
			SEQUENCE { 
				frameNumOfRiu
					Unsigned32,
				slotNumOfRiu
					Unsigned32,
				riuStatus
					INTEGER,
				riuType
					INTEGER,
				activeStandby
					INTEGER,
				groupNumOfRiu
					Unsigned32
			 }

--  用户板框号（所在的LIU单元）
		-- 1.3.6.1.4.1.826318.1.2.3.1.1
		frameNumOfRiu OBJECT-TYPE
			SYNTAX Unsigned32 (1..128)
			MAX-ACCESS read-only
			STATUS current
			DESCRIPTION
				"Description."
			::= { riuInfoEntry 1 }

		
--  用户板槽位号，范围是1～16
		-- 1.3.6.1.4.1.826318.1.2.3.1.2
		slotNumOfRiu OBJECT-TYPE
			SYNTAX Unsigned32 (1..16)
			MAX-ACCESS read-only
			STATUS current
			DESCRIPTION
				"Description."
			::= { riuInfoEntry 2 }

		
--  用户板状态：0表示故障；1表示正常
		-- 1.3.6.1.4.1.826318.1.2.3.1.3
		riuStatus OBJECT-TYPE
			SYNTAX INTEGER
				{
				malfunction(0),
				normal(1)
				}
			MAX-ACCESS read-only
			STATUS current
			DESCRIPTION
				"Description."
			::= { riuInfoEntry 3 }

		
--  用户板类型
		-- 1.3.6.1.4.1.826318.1.2.3.1.4
		riuType OBJECT-TYPE
			SYNTAX INTEGER
				{
				asl(0),
				alt(1),
				em(2),
				mtk(3),
				isdn(4),
				dtk(5),
				dsl(6),
				diu(7),
				riu(10)
				}
			MAX-ACCESS read-only
			STATUS current
			DESCRIPTION
				"Description."
			::= { riuInfoEntry 4 }

		
--  用户板主备状态：0表示备；1表示主
		-- 1.3.6.1.4.1.826318.1.2.3.1.5
		activeStandby OBJECT-TYPE
			SYNTAX INTEGER
				{
				standby(0),
				active(1)
				}
			MAX-ACCESS read-only
			STATUS current
			DESCRIPTION
				"Description."
			::= { riuInfoEntry 5 }

		
--  用户板组号
		-- 1.3.6.1.4.1.826318.1.2.3.1.6
		groupNumOfRiu OBJECT-TYPE
			SYNTAX Unsigned32 (1..256)
			MAX-ACCESS read-only
			STATUS current
			DESCRIPTION
				"Description."
			::= { riuInfoEntry 6 }

		
--  席位信息表定义
		-- 1.3.6.1.4.1.826318.1.2.4
		cwpInfoTable OBJECT-TYPE
			SYNTAX SEQUENCE OF CwpInfoEntry
			MAX-ACCESS not-accessible
			STATUS current
			DESCRIPTION
				"Description."
			::= { tmcsMIBTables 4 }

		
--  席位号区分唯一的席位
		-- 1.3.6.1.4.1.826318.1.2.4.1
		cwpInfoEntry OBJECT-TYPE
			SYNTAX CwpInfoEntry
			MAX-ACCESS not-accessible
			STATUS current
			DESCRIPTION
				"Description."
			INDEX { cwpNum }
			::= { cwpInfoTable 1 }

		
		CwpInfoEntry ::=
			SEQUENCE { 
				cwpNum
					Unsigned32,
				groupNumOfCwp
					Unsigned32,
				cwpStatus
					INTEGER,
				userNameOfCwp
					OCTET STRING,
				leftPhoneOfCwp
					OCTET STRING,
				rightPhoneOfCwp
					OCTET STRING,
				rolesOfCwp
					OCTET STRING
			 }

--  席位号，范围1～128
		-- 1.3.6.1.4.1.826318.1.2.4.1.1
		cwpNum OBJECT-TYPE
			SYNTAX Unsigned32 (1..128)
			MAX-ACCESS read-only
			STATUS current
			DESCRIPTION
				"Description."
			::= { cwpInfoEntry 1 }

		
--  席位组号，范围1～256
		-- 1.3.6.1.4.1.826318.1.2.4.1.2
		groupNumOfCwp OBJECT-TYPE
			SYNTAX Unsigned32 (1..256)
			MAX-ACCESS read-only
			STATUS current
			DESCRIPTION
				"Description."
			::= { cwpInfoEntry 2 }

		
--  席位状态：0表示故障；1表示正常
		-- 1.3.6.1.4.1.826318.1.2.4.1.3
		cwpStatus OBJECT-TYPE
			SYNTAX INTEGER
				{
				malfunction(0),
				normal(1)
				}
			MAX-ACCESS read-only
			STATUS current
			DESCRIPTION
				"Description."
			::= { cwpInfoEntry 3 }

		
--  席位登录用户名
		-- 1.3.6.1.4.1.826318.1.2.4.1.4
		userNameOfCwp OBJECT-TYPE
			SYNTAX OCTET STRING (SIZE (1..32))
			MAX-ACCESS read-only
			STATUS current
			DESCRIPTION
				"Description."
			::= { cwpInfoEntry 4 }

		
--  席位左手柄号码
		-- 1.3.6.1.4.1.826318.1.2.4.1.5
		leftPhoneOfCwp OBJECT-TYPE
			SYNTAX OCTET STRING (SIZE (1..32))
			MAX-ACCESS read-only
			STATUS current
			DESCRIPTION
				"Description."
			::= { cwpInfoEntry 5 }

		
--  席位右手柄号码
		-- 1.3.6.1.4.1.826318.1.2.4.1.6
		rightPhoneOfCwp OBJECT-TYPE
			SYNTAX OCTET STRING (SIZE (1..32))
			MAX-ACCESS read-only
			STATUS current
			DESCRIPTION
				"Description."
			::= { cwpInfoEntry 6 }

		
--  席位登录用户角色
		-- 1.3.6.1.4.1.826318.1.2.4.1.7
		rolesOfCwp OBJECT-TYPE
			SYNTAX OCTET STRING (SIZE (1..96))
			MAX-ACCESS read-only
			STATUS current
			DESCRIPTION
				"Description."
			::= { cwpInfoEntry 7 }

		
		-- 1.3.6.1.4.1.826318.2
		tmcsMIBNofitications OBJECT-IDENTITY
			STATUS current
			DESCRIPTION 
				"Description."
			::= { tmcsMIB 2 }

		
		-- 1.3.6.1.4.1.826318.2.0
		tmcsMIBNotificationPrefix OBJECT-IDENTITY
			STATUS current
			DESCRIPTION 
				"Description."
			::= { tmcsMIBNofitications 0 }

		
--  设备信息变更通知
		-- 1.3.6.1.4.1.826318.2.0.1
		devInfoChange NOTIFICATION-TYPE
			STATUS current
			DESCRIPTION 
				"Description."
			::= { tmcsMIBNotificationPrefix 1 }

		
--  主控板信息变更通知
		-- 1.3.6.1.4.1.826318.2.0.2
		mpuInfoChange NOTIFICATION-TYPE
			STATUS current
			DESCRIPTION 
				"Description."
			::= { tmcsMIBNotificationPrefix 2 }

		
--  用户板信息变更通知
		-- 1.3.6.1.4.1.826318.2.0.3
		riuInfoChange NOTIFICATION-TYPE
			STATUS current
			DESCRIPTION 
				"Description."
			::= { tmcsMIBNotificationPrefix 3 }

		
--  席位信息变更通知
		-- 1.3.6.1.4.1.826318.2.0.4
		cwpInfoChange NOTIFICATION-TYPE
			STATUS current
			DESCRIPTION 
				"Description."
			::= { tmcsMIBNotificationPrefix 4 }

		
--  用户板端口状态通知
		-- 1.3.6.1.4.1.826318.2.0.5
		riuPortsStatus NOTIFICATION-TYPE
			OBJECTS { portNum, frameNumOfPort, slotNumOfPort, portStatus, portType
				 }
			STATUS current
			DESCRIPTION 
				"Description."
			::= { tmcsMIBNotificationPrefix 5 }

		
--  电话按钮信息上报
		-- 1.3.6.1.4.1.826318.2.0.6
		phoneBtnInfos NOTIFICATION-TYPE
			OBJECTS { cwpNumForPhone, phoneBtnNum, phoneBtnName, phoneNum, isDialog, 
				isPhoneBtnEnable, phoneBtnType }
			STATUS current
			DESCRIPTION 
				"Description."
			::= { tmcsMIBNotificationPrefix 6 }

		
--  电台按钮信息上报
		-- 1.3.6.1.4.1.826318.2.0.7
		radioBtnInfos NOTIFICATION-TYPE
			OBJECTS { cwpNumForRadio, radioBtnNum, radioBtnName, frequency, lifesaving, 
				isRadioBtnEnable }
			STATUS current
			DESCRIPTION 
				"Description."
			::= { tmcsMIBNotificationPrefix 7 }

		
--  功能按钮信息上报
		-- 1.3.6.1.4.1.826318.2.0.8
		funcBtnInfos NOTIFICATION-TYPE
			OBJECTS { cwpNumForFunc, funcBtnNum, funcBtnName, funcBtnType }
			STATUS current
			DESCRIPTION 
				"Description."
			::= { tmcsMIBNotificationPrefix 8 }

		
--  通话记录上报
		-- 1.3.6.1.4.1.826318.2.0.9
		callRecords NOTIFICATION-TYPE
			OBJECTS { isConnected, businessType, businessId, causeOfRelease, callingNum, 
				calledNum, thirdpartyNum, makeCallTime, callStartTime, callEndTime
				 }
			STATUS current
			DESCRIPTION 
				"Description."
			::= { tmcsMIBNotificationPrefix 9 }

		
--  用户板网卡状态通知
		-- 1.3.6.1.4.1.826318.2.0.10
		liuEthStatus NOTIFICATION-TYPE
			OBJECTS { lrFlag, devNumOfLiu, eth1StatusOfLiu, eth2StatusOfLiu }
			STATUS current
			DESCRIPTION 
				"Description."
			::= { tmcsMIBNotificationPrefix 10 }

		
--  席位网卡状态上报
		-- 1.3.6.1.4.1.826318.2.0.11
		cwpEthStatus NOTIFICATION-TYPE
			OBJECTS { cwpNumForEth, ethStatusOfCwp }
			STATUS current
			DESCRIPTION 
				"Description."
			::= { tmcsMIBNotificationPrefix 11 }

		
--  席位电源状态上报
		-- 1.3.6.1.4.1.826318.2.0.12
		cwpPowerStatus NOTIFICATION-TYPE
			OBJECTS { cwpNumForPower, powerStatusOfCwp }
			STATUS current
			DESCRIPTION 
				"Description."
			::= { tmcsMIBNotificationPrefix 12 }

		
-- 服务器网络状态上报
		-- 1.3.6.1.4.1.826318.2.0.13
		servEthStatus NOTIFICATION-TYPE
			OBJECTS { servNum, servStatus }
			STATUS current
			DESCRIPTION 
				"Description."
			::= { tmcsMIBNotificationPrefix 13 }

		
		-- 1.3.6.1.4.1.826318.2.2
		tmcsMIBNotificationObjects OBJECT-IDENTITY
			STATUS current
			DESCRIPTION 
				"Description."
			::= { tmcsMIBNofitications 2 }

		
--  设备相关通知类型对象
		-- 1.3.6.1.4.1.826318.2.2.1
		devNotifications OBJECT IDENTIFIER ::= { tmcsMIBNotificationObjects 1 }

		
--  用户板端口状态信息上报
		-- 1.3.6.1.4.1.826318.2.2.1.1
		riuPortInfo OBJECT IDENTIFIER ::= { devNotifications 1 }

		
--  端口号，范围1～256
		-- 1.3.6.1.4.1.826318.2.2.1.1.1
		portNum OBJECT-TYPE
			SYNTAX Unsigned32 (1..256)
			MAX-ACCESS accessible-for-notify
			STATUS current
			DESCRIPTION
				"Description."
			::= { riuPortInfo 1 }

		
--  端口号所属用户板所在框号
		-- 1.3.6.1.4.1.826318.2.2.1.1.2
		frameNumOfPort OBJECT-TYPE
			SYNTAX Unsigned32 (1..128)
			MAX-ACCESS accessible-for-notify
			STATUS current
			DESCRIPTION
				"Description."
			::= { riuPortInfo 2 }

		
--  端口所属用户板所在槽位号
		-- 1.3.6.1.4.1.826318.2.2.1.1.3
		slotNumOfPort OBJECT-TYPE
			SYNTAX Unsigned32 (1..16)
			MAX-ACCESS accessible-for-notify
			STATUS current
			DESCRIPTION
				"Description."
			::= { riuPortInfo 3 }

		
--  端口状态：0表示故障；1表示正常
		-- 1.3.6.1.4.1.826318.2.2.1.1.4
		portStatus OBJECT-TYPE
			SYNTAX INTEGER
				{
				malfunction(0),
				mormal(1)
				}
			MAX-ACCESS accessible-for-notify
			STATUS current
			DESCRIPTION
				"Description."
			::= { riuPortInfo 4 }

		
--  端口类型
		-- 1.3.6.1.4.1.826318.2.2.1.1.5
		portType OBJECT-TYPE
			SYNTAX INTEGER
				{
				asl(0),
				alt(1),
				em(2),
				mtk(3),
				isdn(4),
				dtk(5),
				dsl(6),
				diu(7),
				riu(8),
				yck(9),
				em4(10)
				}
			MAX-ACCESS accessible-for-notify
			STATUS current
			DESCRIPTION
				"Description."
			::= { riuPortInfo 5 }

		
--  通话记录上报
		-- 1.3.6.1.4.1.826318.2.2.1.2
		callRecord OBJECT IDENTIFIER ::= { devNotifications 2 }

		
--  应答类型：0表示未接通；1表示接通
		-- 1.3.6.1.4.1.826318.2.2.1.2.1
		isConnected OBJECT-TYPE
			SYNTAX INTEGER
				{
				disconnected(0),
				connected(1)
				}
			MAX-ACCESS accessible-for-notify
			STATUS current
			DESCRIPTION
				"Description."
			::= { callRecord 1 }

		
--  业务类型：0：普通呼叫；1：席位参与得两方通话；2：表示保持；3：表示取消保持；4：表示监听
-- 5：强插；6：强拆；7：转接；8：转接失败返回；9：代答；10：会议；11：临时会议；12：组呼会议；
-- 13：呼入组呼；14：呼入调度组组呼；15：紧急呼叫；16：查号
		-- 1.3.6.1.4.1.826318.2.2.1.2.2
		businessType OBJECT-TYPE
			SYNTAX INTEGER
				{
				normal(0),
				joinTowSideCall(1),
				callHold(2),
				cancelCallHold(3),
				monitoring(4),
				bargein(5),
				clear(6),
				transit(7),
				transitFailed(8),
				callPickup(9),
				teleconference(10),
				tempTeleconference(11),
				groupCallTeleconference(12),
				inboundGroupCall(13),
				inboundDispatchGroupCall(14),
				emergencyCall(15),
				query(16)
				}
			MAX-ACCESS accessible-for-notify
			STATUS current
			DESCRIPTION
				"Description."
			::= { callRecord 2 }

		
--  业务标识号
		-- 1.3.6.1.4.1.826318.2.2.1.2.3
		businessId OBJECT-TYPE
			SYNTAX OCTET STRING (SIZE (4))
			MAX-ACCESS accessible-for-notify
			STATUS current
			DESCRIPTION
				"Description."
			::= { callRecord 3 }

		
--  释放原因：0：正常挂机；1：用户忙无法呼通；2：没有空闲的中继线路
		-- 1.3.6.1.4.1.826318.2.2.1.2.4
		causeOfRelease OBJECT-TYPE
			SYNTAX INTEGER
				{
				normal(0),
				userBusy(1),
				noRelayLine(2)
				}
			MAX-ACCESS accessible-for-notify
			STATUS current
			DESCRIPTION
				"Description."
			::= { callRecord 4 }

		
--  主叫号码
		-- 1.3.6.1.4.1.826318.2.2.1.2.5
		callingNum OBJECT-TYPE
			SYNTAX OCTET STRING (SIZE (1..16))
			MAX-ACCESS accessible-for-notify
			STATUS current
			DESCRIPTION
				"Description."
			::= { callRecord 5 }

		
--  被叫号码
		-- 1.3.6.1.4.1.826318.2.2.1.2.6
		calledNum OBJECT-TYPE
			SYNTAX OCTET STRING (SIZE (1..16))
			MAX-ACCESS accessible-for-notify
			STATUS current
			DESCRIPTION
				"Description."
			::= { callRecord 6 }

		
--  第三方号码
		-- 1.3.6.1.4.1.826318.2.2.1.2.7
		thirdpartyNum OBJECT-TYPE
			SYNTAX OCTET STRING (SIZE (1..16))
			MAX-ACCESS accessible-for-notify
			STATUS current
			DESCRIPTION
				"Description."
			::= { callRecord 7 }

		
--  发起呼叫时间
		-- 1.3.6.1.4.1.826318.2.2.1.2.8
		makeCallTime OBJECT-TYPE
			SYNTAX Unsigned32
			MAX-ACCESS accessible-for-notify
			STATUS current
			DESCRIPTION
				"Description."
			::= { callRecord 8 }

		
--  呼叫接通时间
		-- 1.3.6.1.4.1.826318.2.2.1.2.9
		callStartTime OBJECT-TYPE
			SYNTAX Unsigned32
			MAX-ACCESS accessible-for-notify
			STATUS current
			DESCRIPTION
				"Description."
			::= { callRecord 9 }

		
--  通话结束时间
		-- 1.3.6.1.4.1.826318.2.2.1.2.10
		callEndTime OBJECT-TYPE
			SYNTAX Unsigned32
			MAX-ACCESS accessible-for-notify
			STATUS current
			DESCRIPTION
				"Description."
			::= { callRecord 10 }

		
-- LIU网卡状态信息上报
		-- 1.3.6.1.4.1.826318.2.2.1.3
		liuEthInfo OBJECT IDENTIFIER ::= { devNotifications 3 }

		
--  LIU左右主控板标记：0表示左侧；1表示右侧
		-- 1.3.6.1.4.1.826318.2.2.1.3.1
		lrFlag OBJECT-TYPE
			SYNTAX INTEGER
				{
				left(0),
				right(1)
				}
			MAX-ACCESS accessible-for-notify
			STATUS current
			DESCRIPTION
				"Description."
			::= { liuEthInfo 1 }

		
--  LIU所属设备的设备号
		-- 1.3.6.1.4.1.826318.2.2.1.3.2
		devNumOfLiu OBJECT-TYPE
			SYNTAX Unsigned32 (1..128)
			MAX-ACCESS accessible-for-notify
			STATUS current
			DESCRIPTION
				"Description."
			::= { liuEthInfo 2 }

		
--  LIU网口1状态：0表示未连接；1表示连接
		-- 1.3.6.1.4.1.826318.2.2.1.3.3
		eth1StatusOfLiu OBJECT-TYPE
			SYNTAX INTEGER
				{
				disconnected(0),
				connected(1)
				}
			MAX-ACCESS accessible-for-notify
			STATUS current
			DESCRIPTION
				"Description."
			::= { liuEthInfo 3 }

		
--  LIU网口2状态：0表示未连接；1表示连接
		-- 1.3.6.1.4.1.826318.2.2.1.3.4
		eth2StatusOfLiu OBJECT-TYPE
			SYNTAX INTEGER
				{
				disconnected(0),
				connected(1)
				}
			MAX-ACCESS accessible-for-notify
			STATUS current
			DESCRIPTION
				"Description."
			::= { liuEthInfo 4 }

		
-- 服务器网络状态信息
		-- 1.3.6.1.4.1.826318.2.2.1.4
		servEthInfo OBJECT IDENTIFIER ::= { devNotifications 4 }

		
-- 服务器号（设备号）
		-- 1.3.6.1.4.1.826318.2.2.1.4.1
		servNum OBJECT-TYPE
			SYNTAX Unsigned32 (1..128)
			MAX-ACCESS accessible-for-notify
			STATUS current
			DESCRIPTION
				"Description."
			::= { servEthInfo 1 }

		
-- 服务器状态：0表示离线；1表示在线
		-- 1.3.6.1.4.1.826318.2.2.1.4.2
		servStatus OBJECT-TYPE
			SYNTAX INTEGER
				{
				offline(0),
				online(1)
				}
			MAX-ACCESS accessible-for-notify
			STATUS current
			DESCRIPTION
				"Description."
			::= { servEthInfo 2 }

		
--  席位相关通知类型对象
		-- 1.3.6.1.4.1.826318.2.2.2
		cwpNotifications OBJECT IDENTIFIER ::= { tmcsMIBNotificationObjects 2 }

		
-- 席位网络状态上报
		-- 1.3.6.1.4.1.826318.2.2.2.1
		cwpEthInfo OBJECT IDENTIFIER ::= { cwpNotifications 1 }

		
--  上报席位网络状态时的席位号
		-- 1.3.6.1.4.1.826318.2.2.2.1.1
		cwpNumForEth OBJECT-TYPE
			SYNTAX Unsigned32 (1..128)
			MAX-ACCESS accessible-for-notify
			STATUS current
			DESCRIPTION
				"Description."
			::= { cwpEthInfo 1 }

		
--  席位网络状态：0表示未连接；1表示连接
		-- 1.3.6.1.4.1.826318.2.2.2.1.2
		ethStatusOfCwp OBJECT-TYPE
			SYNTAX INTEGER
				{
				disconnected(0),
				connected(1)
				}
			MAX-ACCESS accessible-for-notify
			STATUS current
			DESCRIPTION
				"Description."
			::= { cwpEthInfo 2 }

		
-- 席位电源状态上报
		-- 1.3.6.1.4.1.826318.2.2.2.2
		cwpPowerInfo OBJECT IDENTIFIER ::= { cwpNotifications 2 }

		
--  上报席位电源状态时的席位号
		-- 1.3.6.1.4.1.826318.2.2.2.2.1
		cwpNumForPower OBJECT-TYPE
			SYNTAX Unsigned32 (1..128)
			MAX-ACCESS accessible-for-notify
			STATUS current
			DESCRIPTION
				"Description."
			::= { cwpPowerInfo 1 }

		
--  席位电源状态：0表示故障；1表示正常
		-- 1.3.6.1.4.1.826318.2.2.2.2.2
		powerStatusOfCwp OBJECT-TYPE
			SYNTAX INTEGER
				{
				malfunction(0),
				mormal(1)
				}
			MAX-ACCESS accessible-for-notify
			STATUS current
			DESCRIPTION
				"Description."
			::= { cwpPowerInfo 2 }

		
-- 席位电话按钮信息上报
		-- 1.3.6.1.4.1.826318.2.2.2.3
		cwpPhoneBtnInfo OBJECT IDENTIFIER ::= { cwpNotifications 3 }

		
--  上报电话按钮时的席位号
		-- 1.3.6.1.4.1.826318.2.2.2.3.1
		cwpNumForPhone OBJECT-TYPE
			SYNTAX Unsigned32 (1..128)
			MAX-ACCESS accessible-for-notify
			STATUS current
			DESCRIPTION
				"Description."
			::= { cwpPhoneBtnInfo 1 }

		
--  按钮位置
		-- 1.3.6.1.4.1.826318.2.2.2.3.2
		phoneBtnNum OBJECT-TYPE
			SYNTAX Unsigned32 (1..512)
			MAX-ACCESS accessible-for-notify
			STATUS current
			DESCRIPTION
				"Description."
			::= { cwpPhoneBtnInfo 2 }

		
-- 电话按钮名称
		-- 1.3.6.1.4.1.826318.2.2.2.3.3
		phoneBtnName OBJECT-TYPE
			SYNTAX OCTET STRING (SIZE (1..32))
			MAX-ACCESS accessible-for-notify
			STATUS current
			DESCRIPTION
				"Description."
			::= { cwpPhoneBtnInfo 3 }

		
-- 电话按钮对应的电话号码
		-- 1.3.6.1.4.1.826318.2.2.2.3.4
		phoneNum OBJECT-TYPE
			SYNTAX OCTET STRING (SIZE (1..32))
			MAX-ACCESS accessible-for-notify
			STATUS current
			DESCRIPTION
				"Description."
			::= { cwpPhoneBtnInfo 4 }

		
--  是否弹出拨号盘：0表示不弹出；1表示弹出
		-- 1.3.6.1.4.1.826318.2.2.2.3.5
		isDialog OBJECT-TYPE
			SYNTAX INTEGER
				{
				no(0),
				yes(1)
				}
			MAX-ACCESS accessible-for-notify
			STATUS current
			DESCRIPTION
				"Description."
			::= { cwpPhoneBtnInfo 5 }

		
--  是否使能：0表示否；1表示是
		-- 1.3.6.1.4.1.826318.2.2.2.3.6
		isPhoneBtnEnable OBJECT-TYPE
			SYNTAX INTEGER
				{
				no(0),
				yes(1)
				}
			MAX-ACCESS accessible-for-notify
			STATUS current
			DESCRIPTION
				"Description."
			::= { cwpPhoneBtnInfo 6 }

		
--  按钮类型：1：模拟电话；2：中继；3：速拨；4：组拨号； 5：IP电话； 6：磁石电话
-- 7：席位电话；8：中继线路号
		-- 1.3.6.1.4.1.826318.2.2.2.3.7
		phoneBtnType OBJECT-TYPE
			SYNTAX INTEGER
				{
				analogTelephone(1),
				relay(2),
				speedDial(3),
				groupDial(4),
				ipTelephony(5),
				magnetPhone(6),
				cwpPhone(7),
				relayLineNum(8)
				}
			MAX-ACCESS accessible-for-notify
			STATUS current
			DESCRIPTION
				"Description."
			::= { cwpPhoneBtnInfo 7 }

		
-- 席位电台按钮信息上报
		-- 1.3.6.1.4.1.826318.2.2.2.4
		cwpRadioBtnInfo OBJECT IDENTIFIER ::= { cwpNotifications 4 }

		
--  上报电台按钮时的席位号
		-- 1.3.6.1.4.1.826318.2.2.2.4.1
		cwpNumForRadio OBJECT-TYPE
			SYNTAX Unsigned32 (1..128)
			MAX-ACCESS accessible-for-notify
			STATUS current
			DESCRIPTION
				"Description."
			::= { cwpRadioBtnInfo 1 }

		
--  按钮位置
		-- 1.3.6.1.4.1.826318.2.2.2.4.2
		radioBtnNum OBJECT-TYPE
			SYNTAX Unsigned32 (1..512)
			MAX-ACCESS accessible-for-notify
			STATUS current
			DESCRIPTION
				"Description."
			::= { cwpRadioBtnInfo 2 }

		
-- 电台按钮名称
		-- 1.3.6.1.4.1.826318.2.2.2.4.3
		radioBtnName OBJECT-TYPE
			SYNTAX OCTET STRING (SIZE (1..32))
			MAX-ACCESS accessible-for-notify
			STATUS current
			DESCRIPTION
				"Description."
			::= { cwpRadioBtnInfo 3 }

		
--  电台频率
		-- 1.3.6.1.4.1.826318.2.2.2.4.4
		frequency OBJECT-TYPE
			SYNTAX OCTET STRING (SIZE (1..32))
			MAX-ACCESS accessible-for-notify
			STATUS current
			DESCRIPTION
				"Description."
			::= { cwpRadioBtnInfo 4 }

		
--  是否是救生频率：0表示普通：1表示救生
		-- 1.3.6.1.4.1.826318.2.2.2.4.5
		lifesaving OBJECT-TYPE
			SYNTAX INTEGER
				{
				normal(0),
				saving(1)
				}
			MAX-ACCESS accessible-for-notify
			STATUS current
			DESCRIPTION
				"Description."
			::= { cwpRadioBtnInfo 5 }

		
--  是否使能：0表示否；1表示是
		-- 1.3.6.1.4.1.826318.2.2.2.4.6
		isRadioBtnEnable OBJECT-TYPE
			SYNTAX INTEGER
				{
				no(0),
				yes(1)
				}
			MAX-ACCESS accessible-for-notify
			STATUS current
			DESCRIPTION
				"Description."
			::= { cwpRadioBtnInfo 6 }

		
-- 席位功能按钮信息上报
		-- 1.3.6.1.4.1.826318.2.2.2.5
		cwpFuncBtnInfo OBJECT IDENTIFIER ::= { cwpNotifications 5 }

		
--  上报功能按钮时的席位号
		-- 1.3.6.1.4.1.826318.2.2.2.5.1
		cwpNumForFunc OBJECT-TYPE
			SYNTAX Unsigned32 (1..128)
			MAX-ACCESS accessible-for-notify
			STATUS current
			DESCRIPTION
				"Description."
			::= { cwpFuncBtnInfo 1 }

		
--  按钮位置
		-- 1.3.6.1.4.1.826318.2.2.2.5.2
		funcBtnNum OBJECT-TYPE
			SYNTAX Unsigned32 (1..512)
			MAX-ACCESS accessible-for-notify
			STATUS current
			DESCRIPTION
				"Description."
			::= { cwpFuncBtnInfo 2 }

		
-- 功能按钮名称
		-- 1.3.6.1.4.1.826318.2.2.2.5.3
		funcBtnName OBJECT-TYPE
			SYNTAX OCTET STRING (SIZE (1..32))
			MAX-ACCESS accessible-for-notify
			STATUS current
			DESCRIPTION
				"Description."
			::= { cwpFuncBtnInfo 3 }

		
--  功能按钮类型
		-- 1.3.6.1.4.1.826318.2.2.2.5.4
		funcBtnType OBJECT-TYPE
			SYNTAX INTEGER { normal(0) }
			MAX-ACCESS accessible-for-notify
			STATUS current
			DESCRIPTION
				"Description."
			::= { cwpFuncBtnInfo 4 }

		
		-- 1.3.6.1.4.1.826318.3
		tmcsMIBConformance OBJECT-IDENTITY
			STATUS current
			DESCRIPTION 
				"Description."
			::= { tmcsMIB 3 }

		
--  1.3.6.1.4.1.826318.3.1
		-- 1.3.6.1.4.1.826318.3.1
		tmcsMIBCompliances OBJECT-IDENTITY
			STATUS current
			DESCRIPTION 
				"Description."
			::= { tmcsMIBConformance 1 }

		
--  1.3.6.1.4.1.826318.3.2
		-- 1.3.6.1.4.1.826318.3.2
		tmcsMIBGroups OBJECT-IDENTITY
			STATUS current
			DESCRIPTION 
				"Description."
			::= { tmcsMIBConformance 2 }

		
--  1.3.6.1.4.1.826318.3.2.2
		-- 1.3.6.1.4.1.826318.3.2.2
		devGroup OBJECT-GROUP
			OBJECTS { devNum, devType, devName, devNumOfMpu, slotNumOfMpu, 
				mpuStatus, frameNumOfRiu, slotNumOfRiu, riuStatus, riuType, 
				activeStandby, groupNumOfRiu, portNum, frameNumOfPort, slotNumOfPort, 
				portStatus, portType, isConnected, businessType, businessId, 
				callingNum, calledNum, lrFlag, devNumOfLiu, eth1StatusOfLiu, 
				servStatus, servNum, eth2StatusOfLiu, causeOfRelease, thirdpartyNum, 
				makeCallTime, callStartTime, callEndTime }
			STATUS current
			DESCRIPTION 
				"Description."
			::= { tmcsMIBGroups 2 }

		
--  1.3.6.1.4.1.826318.3.2.3
		-- 1.3.6.1.4.1.826318.3.2.3
		cwpGroup OBJECT-GROUP
			OBJECTS { cwpNum, groupNumOfCwp, cwpStatus, userNameOfCwp, leftPhoneOfCwp, 
				rightPhoneOfCwp, rolesOfCwp, ethStatusOfCwp, powerStatusOfCwp, phoneBtnNum, 
				phoneBtnName, phoneNum, isDialog, isPhoneBtnEnable, phoneBtnType, 
				radioBtnNum, radioBtnName, frequency, lifesaving, isRadioBtnEnable, 
				funcBtnNum, funcBtnName, funcBtnType, cwpNumForEth, cwpNumForPower, 
				cwpNumForPhone, cwpNumForRadio, cwpNumForFunc }
			STATUS current
			DESCRIPTION 
				"Description."
			::= { tmcsMIBGroups 3 }

		
--  1.3.6.1.4.1.826318.3.2.4
		-- 1.3.6.1.4.1.826318.3.2.4
		devNotificationGroup NOTIFICATION-GROUP
			NOTIFICATIONS { devInfoChange, mpuInfoChange, riuInfoChange, riuPortsStatus, callRecords, 
				liuEthStatus, servEthStatus }
			STATUS current
			DESCRIPTION 
				"Description."
			::= { tmcsMIBGroups 4 }

		
--  1.3.6.1.4.1.826318.3.2.5
		-- 1.3.6.1.4.1.826318.3.2.5
		cwpNotificationGroup NOTIFICATION-GROUP
			NOTIFICATIONS { cwpInfoChange, phoneBtnInfos, radioBtnInfos, funcBtnInfos, cwpEthStatus, 
				cwpPowerStatus }
			STATUS current
			DESCRIPTION 
				"Description."
			::= { tmcsMIBGroups 5 }

		
	
	END

--
-- HZCHANGRONG-TMCS-MIB.my
--
